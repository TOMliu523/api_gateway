module network_type {
    yang-version 1.1;
    namespace "network_type";
    prefix nt;

    typedef ip_type {
        type enumeration {
            enum IPv4 {
                value 4;
            }
            enum IPv6 {
                value 4;
            }
        }
    }
}

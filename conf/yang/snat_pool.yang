submodule snat_pool {

    // Belongs to the main module (the main module "v1" must define
    // namespace/prefix/imports, etc.)
    belongs-to v1 {
        prefix "v1";
    }

    import types {
        prefix "tys";
    }

    import ietf-inet-types {
        prefix "inet";
    }

    /***********************************************************************
     * SNAT definition: describing source NAT instance configurations.
     * - Key is "name", unique within the global SNAT repository.
     * SNAT instance may be IPv4 or IPv6 type:
     * - v4: defined by (start_addr, end_addr, min_port, max_port).
     * - v6: defined by (start_addr, end_addr, min_port, max_port).
     * Port range must satisfy: 0 < min_port <= max_port <= 65535.
     * Address range must satisfy: start_addr <= end_addr.
     ***********************************************************************/
    container snat_pool {
        list entries {
            key "name";
            description "Source Network Address Translation";

            leaf name {
                type tys:common-name;
                description "SNAT name(1-127 characters, alphanumeric, dash, underscore, dot).";
            }

            leaf interface {
                mandatory true;
                type "tys:interface-name";
                description "Banding interface name.";
            }

            leaf addr-policy {
                type enumeration {
                    enum ip-rr {
                        description "IP round-robin selection among SNAT pool addresses.";
                    }
                    enum conn-rr {
                        description "Connection-based round-robin allocation.";
                    }
                    enum least-conn {
                        description "Select SNAT IP with the least active connections.";
                    }
                    enum preserve-sport {
                        description "Preserve original source port if possible.";
                    }
                }
                default "ip-rr";
                description "Specifies how to allocate source translation addresses in SNAT.";
            }

            // Only one group is supported
            list ip4_entries {
                key "start_addr end_addr";
                leaf start_addr {
                    type inet:ipv4-address;
                    description "IPv4 start address.";
                }

                leaf end_addr {
                    type inet:ipv4-address;
                    description "IPv4 end address.";
                }
            }

            // Only one group is supported
            list ip6_entries {
                key "start_addr end_addr";
                leaf start_addr {
                    type inet:ipv6-address;
                    description "IPv6 start address";
                }

                leaf end_addr {
                    type inet:ipv6-address;
                    description "IPv6 end address";
                }
            }

            must "count(ip4_entries) >= 1 or count(ip6_entries) >= 1" {
                error-message "At least one of ip4_entries or ip6_entries must be present.";
            }

            leaf min_port {
                type inet:port-number;
                default 1024;
                description "TCP/UDP port number (0 .. 65535).";
            }

            leaf max_port {
                type inet:port-number;
                must ". >= ../min_port" {
                    error-message "max_port must be greater than or equal to min_port";
                }
                default 65535;
                description "TCP/UDP port number (0 .. 65535).";
            }
        }
    }
}

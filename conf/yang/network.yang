submodule network {
    belongs-to v1 {
        prefix "v1";
    }

    import ietf-inet-types {
        prefix "inet";
    }

    container arp {
         list items {
            key "ip";
            leaf type {
                mandatory true;
                type enumeration {
                    enum IPv4 {
                        value 4;
                    }
                    enum IPv6 {
                        value 6;
                    }
                }
            }

            leaf ip {
                mandatory true;
                type union {
                    type inet:ipv4-address;
                    type inet:ipv6-address;
                }
                must "(../type='IPv4' and not(contains(., ':'))) or " +
                    "(../type='IPv6' and contains(., ':'))" {
                    error-message "ip address not match address format";
                }
            }

            leaf mac {
                mandatory true;
                type string {
                    pattern '[0-9a-zA-Z]{2}(:[0-9a-zA-Z]{2}){5}';
                }
            }
        }
    }

    container interface {
        list entrys {
            key "name";
            leaf name {
                type string {
                    pattern '[-0-9a-zA-Z.]{3,63}';
                }
            }
            leaf ip {
                mandatory true;
                type union {
                    type inet:ipv4-address;
                    type inet:ipv6-address;
                }
            }
        }
    }
}

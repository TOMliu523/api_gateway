module v1 {
    yang-version 1.1;
    namespace "urn:example:v1";
    prefix v1;

    import ietf-inet-types {
        prefix inet;
    }

    include boot;
    include arp;
    include ipv4;
    include ipv6;

    container query {
        leaf counter {
            type uint64;
            default 0;
            description "Number of query requests.";
        }
    }
}

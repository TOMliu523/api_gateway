submodule account {
    belongs-to v1 {
        prefix "v1";
    }

    container account {
        list users {
            key "username";
            leaf username {
                type string {
                    pattern '[-_a-zA-Z][-_0-9a-zA-Z]{5,30}';
                }
            }
            leaf password {
                type string {
                    pattern '[0-9a-zA-Z+/=.!@#$%^_-]{8,128}';
                }
            }
            leaf role_type {
                type enumeration {
                    enum SYSTEM_ROOT {
                        value 0;
                    }
                    enum SYSTEM_ADMIN {
                        value 1;
                    }
                    enum SYSTEM_AUDIT {
                        value 2;
                    }
                }
            }
            leaf modify_id {
                type uint32;
                default 1;
            }
        }
    }
}

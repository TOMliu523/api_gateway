submodule pool {

    // Belongs to the main module (the main module "v1" must define
    // namespace/prefix/imports, etc.)
    belongs-to v1 {
        prefix "v1";
    }

    import ietf-inet-types {
        prefix "inet";
    }

    import types {
        prefix "tys";
    }

    /********************************************************************
     * Backend server repository: global rserver list
     * Each entry is uniquely identified by the composite key (addr, port).
     ********************************************************************/
    container rserver {
        list entries {
            key "addr port";
            description "Global reusable backend server repository. Key = (addr. port).";

            leaf addr {
                mandatory true;
                type inet:ip-address;
                description "IPv4 or IPv6 address.";
            }

            leaf port {
                type inet:port-number;
                mandatory true;
                description "TCP/UDP port number (0 .. 65535).";
            }

            // TODO
        }
    }

    /***********************************************************************
     * Pool definition: referencing rserver entries from the global list.
     * - Local rserver list uses leafrefs to point to the global repository.
     * - Key is (addr, port), ensuring uniqueness.
     * - rs_count must equal the number of referenced rservers.
     ***********************************************************************/
    container pool {
        list entries {
            key "name";
            description "Virtual service pool definition.";

            leaf name {
                type tys:common-name;
                description "Pool name (1–127 characters, alphanumeric, dash, underscore, dot).";
            }

            leaf algo {
                type enumeration {
                    enum rr {
                        description "Round Robin (default)";
                    }
                    enum random {
                        description "Random selection";
                    }
                    enum wrr {
                        description "Weighted Round Robin";
                    }
                }
                default "rr";
                description "Algorithm used for real server selection. Default is Round Robin.";
            }

            list rserver {
                key "addr port";
                description "References to global rserver entries by (addr, port). No local attributes duplicated.";
                leaf addr {
                    type leafref {
                        path "/v1:rserver/v1:entries/v1:addr";
                    }
                    mandatory true;
                    description "Reference to global rserver IP address.";
                }

                leaf port {
                    type leafref {
                        path "/v1:rserver/v1:entries[v1:addr = current()/../v1:addr]/v1:port";
                    }
                    mandatory true;
                    description "Reference to global rserver port number for the given IP.";
                }

                // TODO
            }
        }
    }
}

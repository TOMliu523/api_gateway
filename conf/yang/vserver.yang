submodule vserver {
    belongs-to v1 {
        prefix "v1";
    }

    import types {
        prefix "tys";
    }

    import ietf-inet-types {
        prefix "inet";
    }

    container vserver {
        list entries {
            key "name";
            description "List of virtual server entries.
                        Each entry defines one virtual server instance identified by name.";

            leaf name {
                type tys:common-name;
                description "Name of the virtual server. Must be unique across all entries.";
            }

            leaf addr {
                mandatory true;
                type inet:ip-address;
                description "Frontend IP address of the virtual server.
                            This is the address on which incoming client connections are accepted.";
            }

            leaf interface {
                mandatory true;
                type "tys:interface-name";
                description "Interface name on which the virtual server is bound.
                            Must refer to an existing system interface (e.g., eth0, bond0, ens1f0.100).";
            }

            leaf port {
                mandatory true;
                type uint16;
                description "Frontend port number on which the virtual server listens for connections.";
            }

            leaf protocol-type {
                type enumeration {
                    enum TCP {
                        description "TCP virtual server (only supported type)";
                    }
                }
                default "TCP";
                description "Transport protocol type used by the virtual server.
                            Currently only TCP is supported, but this field allows
                            for future extension (e.g., UDP).";
            }

            unique "addr port protocol-type";

            leaf pool_name {
                mandatory true;
                type tys:common-name;
                description "Name of the backend pool associated with this virtual server.
                            The backend pool defines the set of real servers to which
                            incoming client connections are forwarded.";
            }

            leaf snat_pool_name {
                mandatory true;
                type tys:common-name;
                description "Name of the SNAT (Source NAT) pool used for source address translation.
                            Specifies which source addresses are used when the virtual
                            server initiates outbound connections to backend servers.";
            }
        }
    }
}
